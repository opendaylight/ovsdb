module hwvtepsouthbound-impl {
    yang-version 1;
    namespace "urn:opendaylight:params:xml:ns:yang:hwvtepsouthbound:impl";
    prefix "hwvtepsouthbound-impl";

    import config { prefix config; revision-date 2013-04-05; }
    import opendaylight-md-sal-binding { prefix md-sal-binding; revision-date 2013-10-28;}
    import opendaylight-entity-ownership-service {prefix eos; revision-date 2015-08-10;}
    import opendaylight-md-sal-dom {prefix dom; revision-date 2013-10-28;}
    import library { prefix library; revision-date 2014-12-10; }

    description
        "Service definition for hwvtepsouthbound project";

    revision "2015-09-01" {
        description
            "Initial revision";
    }

    identity hwvtepsouthbound {
        base config:module-type;
        config:java-name-prefix HwvtepSouthbound;
    }

    augment "/config:modules/config:module/config:configuration" {
        case hwvtepsouthbound {
            when "/config:modules/config:module/config:type = 'hwvtepsouthbound'";
            container broker {
                uses config:service-ref {
                    refine type {
                        mandatory true;
                        config:required-identity md-sal-binding:binding-broker-osgi-registry;
                    }
                }
            }
            container schema-service {
                uses config:service-ref {
                    refine type {
                        mandatory false;
                        config:required-identity dom:schema-service;
                    }
                }
            }
            container clustering-entity-ownership-service {
                uses config:service-ref {
                    refine type {
                        mandatory true;
                        config:required-identity eos:entity-ownership-service;
                    }
                }
            }
            container binding-normalized-node-serializer {
                uses config:service-ref {
                    refine type {
                        mandatory true;
                        config:required-identity md-sal-binding:binding-normalized-node-serializer;
                    }
                }
            }
            container connection-service {
                uses config:service-ref {
                    refine type {
                        mandatory true;
                        config:required-identity library:connection-service;
                    }
                }
            }
        }
    }
}
