module library {
    yang-version 1;
    namespace "urn:opendaylight:params:xml:ns:yang:library:impl";
    prefix "library";

    import config { prefix config; revision-date 2013-04-05; }
    import opendaylight-md-sal-binding { prefix md-sal-binding; revision-date 2013-10-28;}

    description
        "Service definition for library project";

    revision "2014-12-10" {
        description
            "Initial revision";
    }

    identity library {
        base config:module-type;
        config:java-name-prefix Library;
        config:provided-service connection-service;
    }

    identity connection-service {
        base config:service-type;
        config:java-class "org.opendaylight.ovsdb.lib.OvsdbConnection";
    }

    augment "/config:modules/config:module/config:configuration" {
        case library {
            when "/config:modules/config:module/config:type = 'library'";
            container broker {
                uses config:service-ref {
                    refine type {
                        mandatory true;
                        config:required-identity md-sal-binding:binding-broker-osgi-registry;
                    }
                }
            }
            leaf ovsdb-rpc-task-timeout {
                description "Timeout value (in millisecond) after which OVSDB rpc task will be cancelled";
                type uint32;
                default 1000;
            }
        }
    }
}
