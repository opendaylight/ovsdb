module ovsdb-library-impl {
    yang-version 1;
    namespace "urn:opendaylight:params:xml:ns:yang:ovsdb:library:impl";
    prefix "ovsdb-library-impl";

    import config { prefix config; revision-date 2013-04-05; }
    import opendaylight-md-sal-binding { prefix md-sal-binding; revision-date 2013-10-28;}
    import opendaylight-md-sal-dom {prefix dom; revision-date 2013-10-28;}

    description
        "Service definition for the OVSDB library";

    revision "2015-08-19" {
        description
            "Initial revision";
    }

    identity ovsdb-library-impl {
        base config:module-type;
        config:java-name-prefix OvsdbLibraryImpl;
    }

    augment "/config:modules/config:module/config:configuration" {
        case ovsdb-library-impl {
            when "/config:modules/config:module/config:type = 'ovsdb-library-impl'";
            container broker {
                uses config:service-ref {
                    refine type {
                        mandatory true;
                        config:required-identity md-sal-binding:binding-broker-osgi-registry;
                    }
                }
            }
            container binding-normalized-node-serializer {
                uses config:service-ref {
                    refine type {
                        mandatory true;
                        config:required-identity md-sal-binding:binding-normalized-node-serializer;
                    }
                }
            }
            container schema-service {
                uses config:service-ref {
                    refine type {
                        mandatory false;
                        config:required-identity dom:schema-service;
                    }
                }
            }
        }
    }
}
