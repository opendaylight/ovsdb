module netvirt-new-impl {
    yang-version 1;
    namespace "urn:opendaylight:params:xml:ns:yang:netvirt:new:impl";
    prefix "netvirt-impl";

    import config { prefix config; revision-date 2013-04-05; }
    import opendaylight-md-sal-binding { prefix md-sal-binding; revision-date 2013-10-28;}

    description
        "Service definition for netvirt project";

    revision "2015-12-30" {
        description
            "Initial revision";
    }

    identity netvirt {
        base config:module-type;
        config:java-name-prefix Netvirt;
    }

    augment "/config:modules/config:module/config:configuration" {
        case netvirt {
            when "/config:modules/config:module/config:type = 'netvirt'";
            container broker {
                uses config:service-ref {
                    refine type {
                        mandatory true;
                        config:required-identity md-sal-binding:binding-broker-osgi-registry;
                    }
                }
            }
        }
    }
}
