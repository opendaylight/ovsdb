module ovs-nx-sal-cfg {
	yang-version 1;
    namespace "urn:opendaylight:params:xml:ns:yang:controller:config:ovs:nx:sal:config";
    prefix "ovs-nx-sal-cfg";

    import config {prefix config; revision-date 2013-04-05; }

    description
        "openflow extension for nicira - config";

    revision "2014-07-11" {
        description
            "Initial revision";
    }

    identity ovs-nx-sal-provider {
        base config:service-type;
        config:java-class "org.opendaylight.ovs.nx.sal.NiciraExtensionProvider";
    }
}
