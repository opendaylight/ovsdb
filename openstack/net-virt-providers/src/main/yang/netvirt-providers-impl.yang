module netvirt-providers-impl {
    yang-version 1;
    namespace "urn:opendaylight:params:xml:ns:yang:netvirt:providers:impl";
    prefix "netvirt-providers-impl";

    import config { prefix config; revision-date 2013-04-05; }
    import opendaylight-md-sal-binding { prefix md-sal-binding; revision-date 2013-10-28;}
    import opendaylight-entity-ownership-service {prefix eos; revision-date 2015-08-10;}

    description
        "Service definition for netvirt providers project";

    revision "2015-05-13" {
        description
            "Initial revision";
    }

    identity netvirt-providers-impl {
        base config:module-type;
        config:java-name-prefix NetvirtProvidersImpl;
    }

    augment "/config:modules/config:module/config:configuration" {
        case netvirtproviders-impl {
            when "/config:modules/config:module/config:type = 'netvirt-providers-impl'";
            container broker {
                uses config:service-ref {
                    refine type {
                        mandatory true;
                        config:required-identity md-sal-binding:binding-broker-osgi-registry;
                    }
                }
            }

            container clustering-entity-ownership-service {
                uses config:service-ref {
                    refine type {
                        mandatory true;
                        config:required-identity eos:entity-ownership-service;
                    }
                }
            }

            leaf table-offset {
                description "The table-offset is used to set the starting table for the netvirt pipeline";
                type uint8;
            }
        }
    }
}
