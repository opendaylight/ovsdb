module netvirt-sfc-acl {
    yang-version 1;
    namespace "urn:opendaylight:params:xml:ns:yang:netvirt:sfc:acl";
    prefix "acl";

    import ietf-access-control-list { prefix ietf-acl;}
    import yang-ext { prefix ext; }

    revision "2015-01-05" {
        description "Initial revision of netvirt extensions to ietf-acl model";
    }

    augment "/ietf-acl:access-lists/ietf-acl:acl/ietf-acl:access-list-entries/ietf-acl:ace/ietf-acl:matches" {
        description "Neutron network uuid";
        ext:augment-identifier "neutron-network";
        leaf network-uuid {
            type string;
        }
    }

    augment "/ietf-acl:access-lists/ietf-acl:acl/ietf-acl:access-list-entries/ietf-acl:ace/ietf-acl:actions" {
        description "Redirect traffic to SFC identified by either SFC, SFP or RSP";
        ext:augment-identifier "redirect-to-sfc";
        leaf sfc-name {
            type string;
        }
        leaf sfp-name {
            type string;
        }
        leaf rsp-name {
            type string;
        }
        leaf render-rsp {
            type boolean;
            default "false";
        }
    }
}
