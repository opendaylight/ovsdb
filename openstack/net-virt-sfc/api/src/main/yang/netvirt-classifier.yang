module netvirt-sfc-classifier {
    yang-version 1;
    namespace "urn:opendaylight:params:xml:ns:yang:netvirt:sfc:classifier";
    prefix "classifier";

    import ietf-inet-types { prefix inet;}
    import ietf-yang-types { prefix yang;}

    revision "2015-01-05" {
        description "Initial revision of netvirt classifier model";
    }

    container classifiers {
        description "Classifier container which represents the ACL being applied,
                     attachment point and the associated chain";

        list classifier {
            description "A list of SFC classifiers";
            key "name";
            leaf name {
                type string;
            }
            leaf acl {
                type string;
            }
            container sffs {
                list sff {
                    description "The classifier will be attached to these SFFs";
                    key "name";
                    leaf name {
                        type string;
                    }
                }
            }
            container bridges {
                list bridge {
                    key "name";
                    leaf name {
                        type string;
                    }
                    leaf direction {
                        type enumeration {
                            enum ingress;
                            enum egress;
                        }
                    }
                }
            }
        }
    }
}
