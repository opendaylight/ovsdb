module model {
    yang-version 1;
    namespace "urn:opendaylight:params:xml:ns:yang:model";
    prefix "model";

    revision "2015-01-05" {
        description "Initial revision of model model";
    }
}
