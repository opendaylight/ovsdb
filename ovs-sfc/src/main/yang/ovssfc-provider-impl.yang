// vi: set smarttab et sw=4 tabstop=4:
module ovssfc-provider-impl {

  yang-version 1;
  namespace "urn:opendaylight:params:xml:ns:yang:controller:config:ovssfc-provider:impl";
  prefix "ovssfc-provider-impl";

  import config { prefix config; revision-date 2013-04-05; }
  import opendaylight-md-sal-binding { prefix mdsal; revision-date 2013-10-28; }


  description
      "This module contains the base YANG definitions for
      ovssfc-provider impl implementation.";

  revision "2014-06-30" {
      description
          "Initial revision.";
  }

  identity ovssfc-provider-impl {
      base config:module-type;

      config:java-name-prefix OvsSfcProvider;
  }

  augment "/config:modules/config:module/config:configuration" {
    case ovssfc-provider-impl {
      when "/config:modules/config:module/config:type = 'ovssfc-provider-impl'";

      //wires in the data-broker service
      container data-broker {
        uses config:service-ref {
          refine type {
              mandatory false;
              config:required-identity mdsal:binding-async-data-broker;
          }
        }
      }
    }
  }
}
