module routemgr-impl {
    yang-version 1;
    namespace "urn:opendaylight:params:xml:ns:yang:routemgr:impl";
    prefix "routemgr-impl";

    import config { prefix config; revision-date 2013-04-05; }
    import opendaylight-md-sal-binding { prefix md-sal-binding; revision-date 2013-10-28;}
    import opendaylight-md-sal-dom {prefix dom; revision-date 2013-10-28;}

    description
        "Service definition for routemgr project";

    revision "2014-12-10" {
        description
            "Initial revision";
    }

    identity routemgr-impl {
        base config:module-type;
        config:java-name-prefix RoutemgrImpl;
    }

    augment "/config:modules/config:module/config:configuration" {
        case routemgr-impl {
            when "/config:modules/config:module/config:type = 'routemgr-impl'";

 	    leaf routemgr-dummy {
            	 type uint8;
            }
            container broker {
                uses config:service-ref {
                    refine type {
                        mandatory true;
                        config:required-identity md-sal-binding:binding-broker-osgi-registry;
                    }
                }
            }
            container binding-normalized-node-serializer {
                uses config:service-ref {
                    refine type {
                        mandatory true;
                        config:required-identity md-sal-binding:binding-normalized-node-serializer;
                    }
                }
            }
            container schema-service {
                uses config:service-ref {
                    refine type {
                        mandatory false;
                        config:required-identity dom:schema-service;
                    }
                }
            }
            container notification-service {
               uses config:service-ref {
                  refine type {
                    mandatory true;
                    config:required-identity md-sal-binding:binding-notification-service;
                  }
                }
              }
              container data-broker {
                uses config:service-ref {
                  refine type {
                    mandatory false;
                    config:required-identity md-sal-binding:binding-async-data-broker;
                  }
                }
              }
              container rpc-registry {
                uses config:service-ref {
                  refine type {
                    mandatory true;
                    config:required-identity md-sal-binding:binding-rpc-registry;
                  }
                }
              }
        }
    }
}
