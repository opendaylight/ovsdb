module datapath-port-types {
    yang-version 1;
    namespace "urn:opendaylight:params:xml:ns:yang:data-port-types";
    prefix "datapathport";

    import network-topology {prefix "topo"; revision-date "2013-10-21"; }
    import yang-ext { prefix "ext"; }
    import ietf-inet-types { prefix inet; }

    revision "2015-01-28" {
        description "Initial revision of base datapath & port types which would be used by DPDK, among others";
    }

    identity datapath-type-base {
        description "datapath type supported by switch";
    }

    identity port-type-base {
        description "port type supported by switch";
    }

    identity datapath-type-netdev {
        description "Generic netdev datapath type";
        base datapath-type-base;
    }

   identity datapath-type-linux {
        description "Datapath type for linux";
        base datapath-type-base;
    }

   grouping port-type-attributes {
        description "Common leaf for expressing port-type";
        leaf port-type {
                type identityref {
                        base port-type-base;
                }
        }
   }

   grouping datapath-type-attributes {
        description "Common leaf for expressing datapath-type";
        leaf datapath-type {
                type identityref {
                        base datapath-type-base;
                }
        }
   }

   augment "/topo:network-topology/topo:topology/topo:node" {
        description "Augment topology node with a list of supported-port-types";
        ext:augment-identifier "supported-ports";
        list supported-port-types-entry {
                uses port-type-attributes;
        }
   }

   augment "/topo:network-topology/topo:topology/topo:node" {
        description "Augment topology node with a list of supported-datapath-types";
        ext:augment-identifier "supported-datapaths";
        list supported-datapath-types-entry {
                uses datapath-type-attributes;
        }
   }

}
