module dpdk {
    yang-version 1;
    namespace "urn:opendaylight:params:xml:ns:yang:dpdk";
    prefix "dpdk";

    import network-topology {prefix "topo"; revision-date "2013-10-21"; }
    import yang-ext { prefix "ext"; }
    import ietf-inet-types { prefix inet; }
    import datapath-port-types {prefix datapathport;}

    revision "2015-01-26" {
        description "Initial revision of dpdk model";
    }

    identity dpdk-port-type-base {
        description "Base identity for all dpdk-port-types";
    }

    identity dpdk-datapath-type-base {
        description "Datapath type for DPDK";
    }

    identity datapath-type-dpdk-netdev {
        description "Datapath type for DPDK netdev";
        base dpdk-datapath-type-base;
    }

    identity port-type-dpdk {
        description "DPDK port type dpdk"; //CHECK IF THIS IS NEEDED.
        base dpdk-port-type-base;
    }

    identity port-type-dpdkr {
        description "DPDK port type dpdkr";
        base dpdk-port-type-base;
    }

    identity port-type-dpdkvhost {
        description "DPDK port type dpdkvhost";
        base dpdk-port-type-base;
    }

    grouping dpdk-port-type-attributes {
        description "Common leaf for dpdk port types";
        leaf dpdk-port-type {
           type identityref {
              base dpdk-port-type-base;
           }
        }
     }

    grouping datapath-port-locator {
        description "switch datapath and port descriptor";
        leaf datapath {
           type identityref {
             base dpdk-datapath-type-base;
           }
        }
        leaf port {
           type identityref {
             base dpdk-port-type-base;
           }
        }
    }

    augment "/topo:network-topology/topo:topology/topo:node" {
           description "Augment topology with a list of supported dpdk-port-types";
           ext:augment-identifier "supported-datapath-port-parameters";
           list dpdk-port-type-entry {
                 uses dpdk-port-type-attributes;
          }
     }


}
