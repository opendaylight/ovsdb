module hwvtep {
    yang-version 1;
    namespace "urn:opendaylight:params:xml:ns:yang:hwvtep";
    prefix "southbound";

    import network-topology {prefix "topo"; revision-date "2013-10-21"; }
    import yang-ext { prefix "ext"; }
    import ietf-inet-types { prefix inet; revision-date 2010-09-24; }
    import overlay { prefix overlay; }
    import ietf-yang-types { prefix yang; revision-date "2013-07-15";}
    import opendaylight-l2-types { prefix ethertype; revision-date "2013-08-27";}

    revision "2015-01-09" {
        description "Initial revision of southbound model for hwvtep";
    }

    

    typedef hwvtep-physical-switch-ref {
        description "A reference to a hwvtep based physical switch";
        type instance-identifier;
    }

    typedef hwvtep-logical-switch-ref {
        description "A reference to a logical switch in hwvtep based switches";
        type instance-identifier;
    }

    
    typedef hwvtep-physical-locator-ref {
        description "A reference to an endpoint to which logical switch traffic may be encapsulated and forwarded";
        type instance-identifier;
    }

    typedef hwvtep-physical-locator-set-ref {
        description "A reference to a set of endpoints to which logical switch traffic may be encapsulated and forwarded via replication";
        type instance-identifier;
    }

    typedef hwvtep-global-ref {
        description "A reference to an hwvtep global node";
        type instance-identifier;
    }
    
    
    typedef hwvtep-physical-switch-name {
        type string; 
    }

    typedef hwvtep-logical-switch-name {
        type string;
    }
    
    grouping hwvtep-ucast-mac-table-attributes {
        leaf mac-table-entry {
            key "mac-entry";
            leaf mac-entry {
               description "MAC address entry";
               type string;
            }

            leaf logical-switch-ref {
               description "the logical switch to which this mapping applies";
               type hwvtep-logical-switch-ref;
            }

            leaf locator {
               description "Reference to the physical locator to reach this entry";
               type hwvtep-physical-locator-ref;
            }

            leaf ipaddr {
               description " Optional ip address associated with the mac";
               type inet:ip-address;
            }
        }
    }

    grouping hwvtep-mcast-mac-table-attributes {
        leaf mac-table-entry {
            key "mac-entry";
            leaf mac-entry {
               description "MAC address entry";
               type string;
            }

            leaf logical-switch-ref {
               description "the logical switch to which this mapping applies";
               type hwvtep-logical-switch-ref;
            }

            leaf locator-set-ref {
               description "Reference to a set of physical locators used for replication";
               type hwvtep-physical-locator-set-ref;
            }

            leaf ipaddr {
               description " Optional ip address associated with the mac";
               type inet:ip-address;
            }
        }
    }
    
    grouping hwvtep-tunnel-attributes {
        leaf local-locator {
            description "Reference to the physical locator to reach this entry";
               type hwvtep-physical-locator-ref;
        }

        leaf remote-locator {
            description "Reference to the physical locator to reach this entry";
               type hwvtep-physical-locator-ref;
        }

        leaf bfd-config-local {
            type string;
        }

        leaf bfd-config-remote {
            type string;
        }

        leaf bfd-params {
            type string;
        }

    }
    
    grouping hwvtep-physical-switch-attributes {

        leaf physical-switch-name {
            description "The name of the physical switch";
            type hwvtep-physical-switch-name;
        }
        leaf physical-switch-description {
            description "The description of the physical switch";
            type string;
        }
        list management-ips {
            key "ip-address";
            leaf ip-address {
               description "Management IP address of the switch";
               type inet:ip-address;
            }
        }

        leaf managed-by {
            description "The hwvtep global node to which this physical switch belongs to";
            type hwvtep-global-ref;
        }
        
        list tunnel-ips {
            key "ip-address";
            leaf ip-address {
               description "Management IP address of the switch";
               type inet:ip-address;
            }
        }
        
        list tunnels {
            uses hwvtep-tunnel-attributes ;
        }
        list ucast-macs-local {
            uses hwvtep-ucast-mac-table-attributes;
        }

        list ucast-macs-remote {
            uses hwvtep-ucast-mac-table-attributes;
        }
        
        list mcast-macs-local {
            uses hwvtep-mcast-mac-table-attributes;
        }

        list mcast-macs-remote {
            uses hwvtep-mcast-mac-table-attributes;
        }
    }

    grouping hwvtep-global-attributes {
        description "";
        
        list managers {
            description "";
            key "target";
            leaf target {
                description "connection method to manager";
                type inet:uri;
            }
        
            leaf manager-uuid {
                description "The unique identifier of the manager";
                type yang:uuid;
            }
        
            leaf is-connected {
                type boolean;
            }
        
            list manager-other-configs {
                description "Key-value pairs for configuring rarely used features.

                other_config : dscp : optional string
                contains an integer, in the range 0 - 63. DSCP value to be used when establishing a connection to the switch. Default value of 48 if none specified.";
                key "other-config-key";
                leaf other-config-key {
                    description "other-config name/key";
                    type string;
                }
                leaf other-config-value {
                    description "other-config value";
                    type string;
                }
            }
        }
        
        list switches {
            key "switches-ref";
            leaf switches-ref {
                type hwvtep-physical-switch-ref;
            }
        }
        
    }
    
        
    grouping hwvtep-physical-locator-attributes {
        leaf encapsulation-type {
            type string;
            description "Immutable string, must be vxlan_over_ipv4";
        }
        leaf dst-ip {
            type inet:ip-address;
            description "IP address of the locator";
        }
    }

    grouping hwvtep-physical-locator-set-attributes {
        list locators {
            type hwvtep-physical-locator-ref;
        }
    }

    
    grouping hwvtep-logical-switch-attributes {
        leaf logical-switch-uuid {
            description "The unique identifier of the logical switch";
            type yang:uuid;
        }

        leaf logical-switch-name {
            description "The name of the logical switch";
            type hwvtep-logical-switch-name;
        }
        leaf logical-switch-description {
            description "The description of the logical switch";
            type string;
        }

        leaf tunnel-key {
            description "Per Logical Switch tunnel key";
            type string;
        }

    
    }

       
    grouping hwvtep-physical-port-attributes {

        leaf name {
            description "The name of the hwvtep physical port";
            type string;
        }

        leaf description {
            description "The description of the hwvtep physical port";
            type string;
        }

         list vlan-bindings {
            description "A map of vlan ID to logical switch pairs";
            key "vlan-id-key";
            leaf vlan-id-key {
                description "vlan ids in the range 0 - 4095";
                type ethertype:vlan-id;
            }
            leaf logical-switch {
                description "reference to logical switch for the vlan";
                type hwvtep-logical-switch-ref;
            }
        }
    }

   

    augment "/topo:network-topology/topo:topology/topo:node" {
        description "Augmentation for physical switch nodes managed by hwvtep";
        ext:augment-identifier "physical-switch-augmentation";
        uses hwvtep-physical-switch-attributes;
    }

    augment "/topo:network-topology/topo:topology/topo:node" {
        description "Augment topology node for a hwvtep node";
        ext:augment-identifier "hwvtep-global-augmentation";
        uses hwvtep-global-attributes;
    }

    augment "/topo:network-topology/topo:topology/topo:node" {
        description "Augmentation for logical switches for a hwvtep node";
        ext:augment-identifier "hwvtep-logical-switch-augmentation";
        uses hwvtep-logical-switch-attributes;
    }
    
    augment "/topo:network-topology/topo:topology/topo:node" {
        description "Augmentation for physical locator set for a hwvtep node";
        ext:augment-identifier "hwvtep-physical-locator-set-augmentation";
        uses hwvtep-physical-locator-set-attributes;
    }
    augment "/topo:network-topology/topo:topology/topo:node/topo:termination-point" {
        description "Augment topology node termination-point for a hwvtep physical-locator";
        ext:augment-identifier "hwvtep-physical-locator-augmentation";
        uses hwvtep-physical-locator-attributes;
    }
    augment "/topo:network-topology/topo:topology/topo:node/topo:termination-point" {
        description "Augment topology node termination-point for a hwvtep physical-port";
        ext:augment-identifier "hwvtep-physical-port-augmentation";
        uses hwvtep-physical-port-attributes;
    }
}
