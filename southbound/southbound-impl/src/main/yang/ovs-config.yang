/*
Copyright (c) 2016 Inocybe Technology All rights reserved.

This program and the accompanying materials are made available under the
terms of the Eclipse Public License v1.0 which accompanies this distribution,
and is available at http://www.eclipse.org/legal/epl-v10.html INTERNAL
*/

module ovs-config {
    yang-version 1;
    namespace "urn:opendaylight:yang:ovs:config";
    prefix ovs-config;

    description
        "configurations for the OVS instances";

    contact
        "melserngawy@inocybe.com";

    revision "2016-11-16" {
        description
            "Initial revision.";
    }

    container ovs-service-config {
        leaf use-ssl {
            description "Indicate to use TLS communication with the OVS instances";
            type boolean;
        }
        leaf protocols {
            description "The TLS supported protocols ex; SSLv2Hello, TLSv1.1, TLSv1.2";
            type string;
        }
    }
}
